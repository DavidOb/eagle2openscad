if (!board) {
  dlgMessageBox("Run this ULP from a Board", "OK");
  exit (0);
}

real convert(int n,int units)
{
    switch(units) {
        case 0: return u2inch(n);
        case 1: return u2mic(n);
        case 2: return u2mil(n);
        case 3: return u2mm(n);
        case 4: return real(n);
    }
}

board(B) {
    string pattern="";
    string variable_name="partsPositions";
    int include_partname=0;
    int include_partvalue=0;
    int include_comment=0;
    int units=3;
    string units_text[]={"inches","microns (1/1000 mm)","mils (1/1000 inch)","milimeters","internal units (1/320000 mm)"};
    
    int result = dlgDialog("Export settings") {
        dlgLabel("Exports coordinates (in mm) of selected parts as an OpenSCAD array defining a variable.");
        dlgHBoxLayout {
            dlgLabel("RegExp Pattern");
            dlgStringEdit(pattern);
            dlgPushButton("Help") dlgMessageBox("Just use regular expression to match part name :-)\n\n"
            +"A few hints:\n"
            +"Leave empty for all parts\n"
            +"Start with ^ to match from part name start\n"
            +"Use [ACH] to match any of A, C or H\n"
            +"Use . to match any single character\n"
            +"Use * to match zero or more of preceding characters\n"
            +"e.g. ^[RC] will match all parts whose name starts with R or C, typically all resistors + all capacitors\n"
            +"^[RC].*2 will match all parts whose name starts with R or C and ends with 2, e.g. R2, R12, C42 and such\n"
            +"\n... or simply write whichever regexp you like.\n"
            );
        }
        dlgHBoxLayout {
            dlgLabel("OpenSCAD variable name:");
            dlgStringEdit(variable_name);
        }
        dlgCheckBox("Include part &name",include_partname);
        dlgCheckBox("Include part &value",include_partvalue);
        dlgHBoxLayout {
            dlgLabel("     ");
            dlgCheckBox("... include it as a &comment",include_comment);
            dlgStretch(1);
        }
        dlgHBoxLayout {
            dlgLabel("Units:");
            dlgComboBox(units_text,units);
            dlgStretch(1);
        }
        dlgHBoxLayout {
            dlgStretch(1);
            dlgPushButton("+OK") dlgAccept();
            dlgPushButton("-Cancel") dlgReject(-1);
        }
    };
    if (result < 0) {
        exit(0);
    }

    string file_name = dlgFileSave("Export to file","","OpenSCAD files (*.scad *.txt);;Any file type (*.*)");
    if (file_name=="") {
        dlgMessageBox("No file selected - exiting.", "OK");
        exit(0);
    }

    output(file_name) {
        string partname="";
        string partvalue="";
        string comment="";
        printf(variable_name+" = [\n");

        if(include_comment && (include_partname || include_partvalue)) {
            comment="// ";
            if(include_partname) comment += "name ";
            if(include_partvalue) comment += "value";
        } else {
            if(include_partname) partname=", name"; else partname="";
            if(include_partvalue) partvalue=", value"; else partvalue="";
        }
        printf("// Selection pattern: %s\n",pattern);
        printf("// Units: %s\n",units_text[units]);
        printf("//[   x   ,   y   %s%s ], %s\n",partname,partvalue,comment);

        B.elements(E) if (E.populate) {
          if( strxstr(E.name, pattern) >= 0 ) {
              comment="";
              if(include_comment && (include_partname || include_partvalue)) {
                  comment="// ";
                  if(include_partname) comment += E.name+" ";
                  if(include_partvalue) comment += E.value;
              } else {
                  if(include_partname) partname=", \""+E.name+"\""; else partname="";
                  if(include_partvalue) partvalue=", \""+E.value+"\""; else partvalue="";
              }
              printf("  [ %6.2f, %6.2f%s%s ], %s\n", convert(E.x,units), convert(E.y,units),partname,partvalue,comment);
          }
        }
        printf("];\n");
        dlgMessageBox("Exported to "+file_name, "OK");
    }
}
